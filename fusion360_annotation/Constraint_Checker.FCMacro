import os
import re
import FreeCAD as App
import FreeCADGui as Gui
import Sketcher

def test_constraints():
    sk = None
    try:
        sk = Gui.ActiveDocument.getInEdit().Object
    except:
        pass

    if sk is None:
        print("Error: sketch is not selected. Open the sketch and try again.")
        return
    print(f"Sketch: {sk.Name}, DoF: {sk.solve()}")

    errors = []

    # 1. Tautology Detection (e.g., Equal(A,A))
    for i, c in enumerate(sk.Constraints):
        if c.Type in ["Equal"] and c.First == c.Second and c.First != -2000:
            errors.append(f"[TAUTOLOGY] #{i + 1} {c.Type}(Edge{c.First + 1}, Edge{c.Second + 1})")

    # 2. External Reference Detection (e.g., -1=X-axis, -2=Y-axis)
    for i, c in enumerate(sk.Constraints):
        for r in [c.First, c.Second, c.Third]:
            if r in (-1, -2):
                errors.append(f"[EXT REF] #{i + 1} {c.Type} references {'X-axis' if r == -1 else 'Y-axis'}")
                break

    # 3. Check if there is only one Block constraint, and if removing it results in DoF=2
    blocks = [(i, c) for i, c in enumerate(sk.Constraints) if c.Type == "Block"]
    if len(blocks) != 1:
        errors.append(f"[BLOCK] Block constraint count = {len(blocks)} (expected 1)")
    else:
        bi, bc = blocks[0]
        sk.delConstraint(bi)
        App.ActiveDocument.recompute()
        dof_without_block = sk.DoF
        sk.addConstraint(Sketcher.Constraint("Block", bc.First))
        App.ActiveDocument.recompute()
        if dof_without_block != 2:
            errors.append(f"[BLOCK] DoF without Block = {dof_without_block} (expected 2)")
        else:
            print("[BLOCK] OK: DoF without Block = 2")

    # 4. Check primitive deletion/reordering
    fc_file = App.ActiveDocument.FileName
    if fc_file:
        py_file = os.path.splitext(fc_file)[0] + ".py"
        if os.path.exists(py_file):
            try:
                with open(py_file, 'r', encoding='utf-8') as f:
                    lines = f.readlines()

                ori_geos_info = []
                for line in lines:
                    m = re.search(r"addGeometry\(Part\.([A-Za-z]+).*?,\s*(True|False)\)", line)
                    if m:
                        ori_geos_info.append({
                            "type": m.group(1),
                            "const": (m.group(2) == 'True')
                        })

                tgt_geos = sk.Geometry

                if len(tgt_geos) < len(ori_geos_info):
                    errors.append(f"[PRIMITIVE] Count mismatch: original has {len(ori_geos_info)}, but current has only {len(tgt_geos)}. You cannot delete original primitives.")
                
                for idx in range(len(tgt_geos)):
                    tg = tgt_geos[idx]
                    tg_type = tg.__class__.__name__
                    is_const = sk.getConstruction(idx)
                    
                    if idx < len(ori_geos_info):
                        ori = ori_geos_info[idx]
                        if ori["type"] != tg_type:
                            errors.append(f"[PRIMITIVE] Type mismatch at index {idx}: original is {ori['type']}, current is {tg_type}.")
                        elif ori["const"] != is_const:
                            errors.append(f"[PRIMITIVE] Construction mismatch at index {idx}. You cannot change the construction state of original primitives.")
                    else:
                        if not is_const:
                            errors.append(f"[PRIMITIVE] Added primitive at index {idx} ({tg_type}) must be a construction geometry.")

            except Exception as e:
                print(f"Warning: Failed to verify primitives: {e}")
        else:
            print(f"Warning: Original script not found: {py_file}")
    else:
        print("Warning: Document not saved to a file, skipping primitive check.")

    # --- Outputs ---
    if errors:
        print("\n=== ERRORS FOUND ===")
        for e in errors: print(e)
        print("*** Delete constraints from '''BOTTOM to TOP''', as the indices change by deletion. ***")
    else:
        print("\nAll checks passed.")


test_constraints()
